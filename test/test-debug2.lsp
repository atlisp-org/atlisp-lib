(test:clear)
(princ "Starting...\n")
(test:suite 'string)
(princ "Suite created\n")
(defvar *result* nil)
(setq *result* (mapcar '(lambda (s)
                         (princ (strcat "Checking: " (vl-princ-to-string (car s)) "\n"))
                         (if (eq (car s) 'string)
                             (progn
                               (princ "Found string suite, adding case\n")
                               (cons s (list (list 'test1 '((lambda () "result")) "result"))))
                           s))
                       *test-suite*))
(princ "Result:\n")
(princ (vl-princ-to-string *result*))
