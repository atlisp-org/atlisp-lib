(defun geometry:ucs-angle nil (if (equal 0 (car (getvar "ucsxdir"))
      1.0e-08)
  (if (equal 1 (cadr (getvar "ucsxdir"))
    1.0e-08)
      (* 0.5 pi)
      (* 1.5 pi))
  (if (>= (cadr (getvar "ucsxdir"))
    0)
      (atan (/ (cadr (getvar "ucsxdir"))
          (car (getvar "ucsxdir"))))
      (+ pi (atan (/ (cadr (getvar "ucsxdir"))
      (car (getvar "ucsxdir"))))))))
