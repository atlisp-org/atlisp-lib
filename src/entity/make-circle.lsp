(defun entity:make-circle (pts-cen num-rad / *error*)
  "创建圆。如果圆心是点的列表或半径是数值的列表，可以同时创建多个圆"
  "图元名或图元名列表 - 成功返回图元名，失败返回nil"
  "(entity:make-circle (getpoint) 5)"
  "(entity:make-circle (list (getpoint) (getpoint)) '(3 5))"
  (defun *error* (msg)
  (princ (strcat "entity:make-circle 错误: " msg))
  nil)
  (cond
   ((and (= (quote point) (type-of pts-cen)) (numberp num-rad))
  (entmakex (list (quote (0 . "circle"))
      (quote (100 . "AcDbEntity"))
      (quote (100 . "AcDbCircle"))
      (cons 10 pts-cen)
      (cons 40 num-rad))))
   ((and (listp pts-cen) (apply (quote and) (mapcar (function (lambda (x) (= (quote point) (type-of x)))) pts-cen)))
  (mapcar (quote (lambda (pt) (entity:make-circle pt num-rad))) pts-cen))
   ((and (listp num-rad) (apply (quote and) (mapcar (quote numberp) num-rad)))
  (mapcar (quote (lambda (rad) (entity:make-circle pts-cen rad))) num-rad))
   (t (@:log "WARR" "参数错误,无创建圆") nil)))
