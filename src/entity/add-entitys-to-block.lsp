(defun entity:add-entitys-to-block (block ss / lst mat)
  "添加选择集到块定义。"
  (setq lst (pickset->vlalist ss)
  mat (entity:reference->definition block)
  mat (vlax-tmatrix (append (mapcar (quote append)
          (car mat)
          (mapcar (quote list)
      (cadr mat)))
    (quote ((0.0 0.0 0.0 1.0))))))
  (foreach obj lst (vla-transformby obj mat))
  (vla-copyobjects (std:active-document)
  (vla:objarray lst)
  (vla-item (vla-get-blocks (std:active-document))
      (vla-get-name block)))
  (foreach obj lst (vla-delete obj))
  (vla-regen (std:active-document)
  acallviewports))
