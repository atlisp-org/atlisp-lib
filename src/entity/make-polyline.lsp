(defun entity:make-polyline (pts closed / ent)
  "生成三维多段线.POLYLINE\n参数:\n  pts:端点坐标点表，如：((x1 y1 z1)
  (x2 y2 z2)
  (x2 y2 z2))\n  closed:是否闭合，1:闭合，0：不闭合"
  "生成多段线的图元名"
  "(entity:make-pline '((0 0 0)
      (5000 0 0)
      (5000 5000 0)
      (0 5000 0))
  1)"
  (if (= closed 1)
  (entmake (list (quote (0 . "POLYLINE"))
    (quote (66 . 1))
    (quote (10 0.0 0.0 0.0))
    (quote (70 . 9))))
  (entmake (list (quote (0 . "POLYLINE"))
    (quote (66 . 1))
    (quote (70 . 8)))))
  (if pts (mapcar (quote (lambda (x)
          (entmake (list (cons 0 "VERTEX")
              (cons 10 x)
              (cons 70 32)))))
      pts))
  (entmake (quote ((0 . "SEQEND"))))
  (entlast))
