(defun entity:make-rectangle (pt1 pt2)
  "创建矩形框(水平，竖直方向)"
  (entmake (list (quote (0 . "LWPOLYLINE"))
      (quote (100 . "AcDbEntity"))
      (quote (100 . "AcDbPolyline"))
      (quote (90 . 4))
      (quote (70 . 1))
      (if (caddr pt1)
    (cons 38 (caddr pt1))
    (cons 38 0))
      (cons 10 (list (car pt1)
          (cadr pt1)))
      (cons 10 (list (car pt2)
          (cadr pt1)))
      (cons 10 (list (car pt2)
          (cadr pt2)))
      (cons 10 (list (car pt1)
          (cadr pt2)))
      (cons 210 (quote (0 0 1)))))
  (entlast))
