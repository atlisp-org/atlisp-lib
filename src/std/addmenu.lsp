(defun std:addmenu (menugroupname popname popitems insertbeforeitem / i menubar menuitem n popupmenu)
  (std:removemenuitem popname)
  (setq menubar (vla-get-menubar (vlax-get-acad-object)))
  (if insertbeforeitem (progn (setq n (vla-get-count menubar))
      (setq i (1- n))
      (while (and (>= i 0)
          (/= insertbeforeitem (vla-get-name (setq menuitem (vla-item menubar i)))))
        (setq i (1- i)))
      (if (< i 0)
        (setq i (vla-get-count menubar))))
    (setq i (vla-get-count menubar)))
  (if (not (setq popupmenu (std:catchapply (quote vla-item)
          (list (vla-get-menus (vla-item (vla-get-menugroups (vlax-get-acad-object))
                menugroupname))
            popname))))
    (setq popupmenu (vla-add (vla-get-menus (vla-item (vla-get-menugroups (vlax-get-acad-object))
            menugroupname))
        popname)))
  (vlax-for popupmenuitem popupmenu (vla-delete popupmenuitem))
  (vla-insertinmenubar popupmenu i)
  (std:insertpopmenuitems popupmenu popitems)
  (princ))
