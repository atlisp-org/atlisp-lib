(defun std:addtoolbars (menugroupname toolbaritems / flyout flyoutbutton helpstring idx items largeiconname left macro menugroupobj name smalliconname toolbar toolbaritem toolbarname toolbars top)
  (if (not (setq menugroupobj (std:catchapply vla-item (list (vla-get-menugroups (vlax-get-acad-object))
            menugroupname))))
    (progn (alert (strcat "菜单组\""
          menugroupname "\"不存在！无法加载菜单条！"))
      (exit)))
  (setq toolbars (vla-get-toolbars menugroupobj))
  (foreach items toolbaritems (setq toolbarname (car items)
      left (cadr items)
      top (caddr items)
      items (cdddr items))
    (if (setq toolbar (std:catchapply vla-item (list toolbars toolbarname)))
      (vla-delete toolbar))
    (setq toolbar (vla-add toolbars toolbarname))
    (vla-put-left toolbar left)
    (vla-put-top toolbar top)
    (setq idx 0)
    (foreach lst items (setq name (car lst)
        helpstring (cadr lst)
        macro (caddr lst)
        smalliconname (cadddr lst)
        largeiconname (car (cddddr lst))
        flyoutbutton (cadr (cddddr lst)))
      (if (not largeiconname)
        (setq largeiconname smalliconname))
      (if flyoutbutton (setq flyout :vlax-true)
        (setq flyout :vlax-false))
      (setq toolbaritem (std:catchapply vla-addtoolbarbutton (list toolbar idx name helpstring macro flyout)))
      (std:catchapply vla-setbitmaps (list toolbaritem smalliconname largeiconname))
      (if flyoutbutton (std:catchapply vla-attachtoolbartoflyout (list toolbaritem menugroupname flyoutbutton)))
      (setq idx (1+ idx)))))
