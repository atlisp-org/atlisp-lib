(defun block:get-dynamic-properties (blk / oblk props)
  "获取动态块的动态特性(自定义)列表：特性名，当前值，只读性，是否显示，允许值"
  (if (= (quote ename)
      (type blk))
  (progn (setq oblk (vlax-ename->vla-object blk))
      (setq props (vlax-invoke oblk (quote getdynamicblockproperties)))
      (list (mapcar (quote (lambda (x)
              (vlax-get-property x (quote propertyname))))
          props)
    (mapcar (quote (lambda (x)
              (vlax-get-property x (quote value))))
          props)
    (mapcar (quote vla-get-readonly)
          props)
    (mapcar (quote vla-get-show)
          props)
    (mapcar (quote (lambda (x)
              (vlax-get-property x (quote allowedvalues))))
          props)))
  nil))
