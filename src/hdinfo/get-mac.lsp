(defun hdinfo:get-mac (/ i mac s str svr wmi)
  "获取mac地址，不一定有用。"
  (vl-load-com)
  (setq wmi (vlax-create-object "WbemScripting.SWbemLocator"))
  (setq svr (vlax-invoke wmi (quote connectserver)))
  (setq str "Select * from Win32_NetworkAdapterConfiguration Where IPEnabled=TRUE")
  (setq mac (vlax-invoke svr (quote execquery)
      str))
  (vlax-for i mac (setq s (cons (vlax-get i (quote macaddress))
    s)))
  (vlax-release-object mac)
  (vlax-release-object svr)
  (vlax-release-object wmi)
  (car s))
