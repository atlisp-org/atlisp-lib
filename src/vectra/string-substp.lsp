(defun vectra:string-substp (str find repl p / pos len)
  (setq len (strlen find)
  pos 0 occ 0)
  (while (and (setq pos (vl-string-search find str pos))
      (< (setq occ (1+ occ))
    p))
  (setq pos (+ pos len)))
  (if (= occ p)
  (vl-string-subst repl find str pos)
  str))
