(defun vectra:entmake (dxf / r)
  (vectra:linetype-get $addnew-linetype)
  (vl-catch-all-apply (quote entmakex)
  (list (append dxf (list (cons 8 $addnew-layer)
          (cons 6 $addnew-linetype)
          (cons 62 $addnew-color)
          (cons 370 $addnew-lineweight)))))
  (setq r (entlast))
  (if (null (vl-catch-all-error-p r))
  (if $addnew-xdata (vectra:xdata-set r (car $addnew-xdata)
    (cdr $addnew-xdata))))
  r)
