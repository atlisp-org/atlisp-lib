(defun vectra:error-handler (s)
  (if (or (= s "Function cancelled")
      (= s "quit / exit abort")
      (= s "函数被取消"))
  (princ)
  (princ s))
  (while (not (equal (getvar "CMDNAMES")
    ""))
  (command nil))
  (vectra:osnap-restore)
  (vectra:endundomark)
  (vectra:error-end)
  (princ))
