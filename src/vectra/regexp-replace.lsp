(defun vectra:regexp-replace (str pattern new / reg r)
  (setq reg (vlax-create-object "vbscript.regexp"))
  (vlax-put-property reg (quote pattern)
  pattern)
  (vlax-put-property reg (quote global)
  1)
  (vlax-put-property reg (quote ignorecase)
  1)
  (setq r (vlax-invoke reg (quote replace)
      str new))
  (vlax-release-object reg)
  r)
