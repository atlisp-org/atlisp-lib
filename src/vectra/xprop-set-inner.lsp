(defun vectra:xprop-set-inner (ename appname prop datadef / xdata xdata2 tmp)
  (if (atom (car prop))
  (setq prop (list prop)))
  (setq prop (vl-remove-if (quote (lambda (e)
          (or (null (car e))
      (= ""
              (car e))
      (null (cdr e))
      (vl-catch-all-error-p (cdr e)))))
      prop))
  (if prop (progn (setq xdata (vectra:xdata-get ename appname))
      (while xdata (if (setq tmp (assoc (cdar xdata)
              prop))
          (setq xdata2 (cons (car xdata)
              xdata2)
      xdata2 (cons (cons (caadr xdata)
        (cdr tmp))
              xdata2)
      prop (vl-remove tmp prop))
          (setq xdata2 (cons (car xdata)
              xdata2)
      xdata2 (cons (cadr xdata)
              xdata2)))
    (setq xdata (cddr xdata)))
      (if prop (foreach e prop (setq xdata2 (append (reverse (vectra:xprop-pack1 e datadef))
              xdata2))))
      (setq xdata2 (reverse xdata2))
      (vectra:xdata-set ename appname xdata2))))
