(defun vectra:string-tokenize (str delim / buff l2)
  (setq str (vl-string->list str)
  delim (vl-string->list delim))
  (while str (if (member (car str)
    delim)
      (setq l2 (cons (vl-list->string (reverse buff))
          l2)
    buff nil)
      (setq buff (cons (car str)
          buff)))
  (setq str (cdr str)))
  (setq l2 (cons (vl-list->string (reverse buff))
      l2))
  (reverse l2))
