(defun vectra:template-parse-inner (template gs ge / buff ch result)
  (setq template (vl-string->list template))
  (while (setq ch (car template))
  (cond ((= ch (ascii gs))
    (if buff (setq result (cons (vl-list->string (reverse buff))
              result)
      buff nil)))
      ((= ch (ascii ge))
    (if buff (setq result (cons (list (vl-list->string (reverse buff)))
              result)
      buff nil)))
      (t (setq buff (cons ch buff))))
  (setq template (cdr template)))
  (if buff (setq result (cons (vl-list->string (reverse buff))
    result)))
  (mapcar (function (lambda (e)
    (if (atom e)
          e (vectra:string-tokenize (car e)
      ":"))))
  (reverse result)))
