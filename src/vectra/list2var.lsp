(defun vectra:list->var (lsp / e n var)
  (if (vl-consp lsp)
  (progn (setq n (1- (length lsp))
    var (vlax-make-safearray vlax-vbvariant (cons 0 n)))
      (vlax-safearray-fill var (mapcar (quote (lambda (e)
              (vectra:list->var e)))
          lsp))
      var)
  (vlax-make-variant lsp)))
