(defun entity:make-arc (cen rad startpt endpt)
  "创建圆弧"
  (entmakex (list (quote (0 . "ARC"))
      (quote (100 . "AcDbEntity"))
      (quote (100 . "AcDbCircle"))
      (quote (100 . "AcDbArc"))
      (cons 10 cen)
      (cons 40 rad)
      (cons 50 (if (listp startpt)
          (angle cen startpt)
          startpt))
      (cons 51 (if (p:listp endpt)
          (angle cen endpt)
          endpt)))))
