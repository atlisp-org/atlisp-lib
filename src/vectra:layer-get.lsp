(defun vectra:layer-get (name conf / dxf layer)
  (if (null (setq layer (tblsearch "LAYER"
          name)))
    (progn (setq dxf (list (quote (0 . "LAYER"))
          (quote (100 . "AcDbSymbolTableRecord"))
          (quote (100 . "AcDbLayerTableRecord"))
          (quote (70 . 0))
          (quote (6 . "Continuous"))
          (cons 2 name)))
      (if (car conf)
        (setq dxf (append dxf (list (cons 62 (atoi (car conf)))))))
      (if (cadr conf)
        (progn (vectra:linetype-get (cadr conf))
          (setq dxf (append dxf (list (cons 6 (cadr conf)))))))
      (if (caddr conf)
        (setq dxf (append dxf (list (cons 370 (atoi (caddr conf)))))))
      (if (and (not (null (cadddr conf)))
          (= "FALSE"
            (strcase (cadddr conf))))
        (setq dxf (append dxf (list (cons 290 0)))))
      (entmake dxf))
    layer))
