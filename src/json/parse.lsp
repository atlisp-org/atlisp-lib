(defun json:parse (str / lst-str flag-escape flag-quote flag-keylevel flag-arraylevel atom-str-lst pre-char curr-char)
  "JSON 字符串转化为 Lisp 列表"
  "list - 返回解析后的列表，解析失败返回nil"
  (setq lst-str (vl-string->list str))
  (setq flag-escape nil)
  (setq flag-quote nil)
  (setq flag-keylevel 0)
  (setq flag-arraylevel 0)
  (setq atom-str-lst '())
  (while lst-str
  (setq curr-char (car lst-str))
  (cond
     ((= (ascii "\\") curr-char)
      (setq flag-escape (not flag-escape))
      (setq atom-str-lst (cons curr-char atom-str-lst)))
     ((and (= (ascii "\"") curr-char) (null flag-escape))
      (setq flag-escape nil)
      (setq flag-quote (not flag-quote))
      (setq atom-str-lst (cons curr-char atom-str-lst)))
     (t
      (setq flag-escape nil)
      (if flag-quote
    (setq atom-str-lst (cons curr-char atom-str-lst))
    (cond
         ((= (ascii "{") curr-char)
          (setq flag-keylevel (1+ flag-keylevel))
          (setq atom-str-lst (cons (ascii "(") atom-str-lst)))
         ((= (ascii "[") curr-char)
          (setq flag-arraylevel (1+ flag-arraylevel))
          (if (= pre-char (ascii ":"))
      (setq atom-str-lst (cons (ascii "(") (cdddr atom-str-lst)))
      (setq atom-str-lst (cons (ascii "(") atom-str-lst))))
         ((= (ascii "}") curr-char)
          (setq flag-keylevel (1- flag-keylevel))
          (setq atom-str-lst (cons (ascii ")") atom-str-lst)))
         ((= (ascii "]") curr-char)
          (setq flag-arraylevel (1- flag-arraylevel))
          (setq atom-str-lst (cons (ascii ")") atom-str-lst)))
         ((= (ascii ":") curr-char)
          (setq atom-str-lst (cons (ascii " ") (cons (ascii ".") (cons (ascii " ") atom-str-lst)))))
         ((= (ascii ",") curr-char)
          (setq atom-str-lst (cons (ascii "(") (cons (ascii ")") atom-str-lst))))
         (t (setq atom-str-lst (cons curr-char atom-str-lst)))))))
  (setq pre-char curr-char)
  (setq lst-str (cdr lst-str)))
  (read (strcat "(" (vl-list->string (reverse atom-str-lst)) ")")))
