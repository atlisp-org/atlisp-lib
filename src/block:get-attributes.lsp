(defun block:get-attributes (blk / lst)
  "获取块属性,返回属性名和值的点对列表。"
  (if (= (quote ename)
      (type blk))
    (if (safearray-value (setq lst (vlax-variant-value (vla-getattributes (vlax-ename->vla-object blk)))))
      (mapcar (quote (lambda (x)
            (cons (vla-get-tagstring x)
              (vla-get-textstring x))))
        (vlax-safearray->list lst)))
    nil))
