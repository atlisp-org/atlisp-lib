(defun-q string:number2chinese(num / charofcash i n tempa tempstr)
  "将数字转化为汉语大写.,仅支持到万亿，只支持整数"
  "String"
  "(string:number2chinese 3587823416)"
  (defun _n2big (str)      
  (setq str (string:subst-all "壹" "1" str))
  (setq str (string:subst-all "贰" "2" str))
  (setq str (string:subst-all "叁" "3" str))
  (setq str (string:subst-all "肆" "4" str))
  (setq str (string:subst-all "伍" "5" str))
  (setq str (string:subst-all "陆" "6" str))
  (setq str (string:subst-all "柒" "7" str))
  (setq str (string:subst-all "捌" "8" str))
  (setq str (string:subst-all "玖" "9" str))
  ;;(setq str (string:subst-all "零" "0" str))
  ;; (while (wcmatch str "*零零*")
  ;;   (setq str (string:subst-all "零" "零零" str)))

  )
  (setq num (rtos num 2 0))
  (setq i -1 CharOfCash "")
  (setq n(strlen num))
  (repeat n
          (setq i(1+ i))
          (setq TempStr(substr num (- n i)1))
          
          ;;(setq TempStr (_n2big TempStr))
          (cond
           ((= i 0)
      (if (= "零" TempStr)
        (setq TempStr "")
              )
      )
           ((= i 1)
      (if (/= "零" TempStr)
        (setq TempStr (strcat TempStr "拾"))
              )
      )
           ((= i 2)
      (if (/= "零" TempStr)
        (setq TempStr (strcat TempStr "百"))
              )
      )                        
           ((= i 3)
      (if (/= "零" TempStr)
        (setq TempStr (strcat TempStr "千"))
              )
      )               
           ((= i 4)
      (if (= "零" TempStr)
        (setq TempStr  "万")
              (setq TempStr (strcat TempStr "万"))
              )
      )               
           ((= i 5)
      (if (/= "零" TempStr)
        (setq TempStr (strcat TempStr "十"))
              )
      )        
           ((= i 6)
      (if (/= "零" TempStr)
        (setq TempStr (strcat TempStr "百"))
              )
      )
           ((= i 7)
      (if (/= "零" TempStr)
        (setq TempStr (strcat TempStr "千"))
              )
      )
           ((= i 8)
      (if (= "零" TempStr)
        (setq TempStr  "亿")
              (setq TempStr (strcat TempStr "亿"))
              )
      )
           ((= i 9)
      (if (/= "零" TempStr)
        (setq TempStr (strcat TempStr "十"))
              )
      )
           ((= i 10)
      (if (/= "零" TempStr)
        (setq TempStr (strcat TempStr "百"))
              )
      )
           ((= i 11)
      (if (/= "零" TempStr)
        (setq TempStr (strcat TempStr "千"))
              )
      )
           ((= i 12)
      (if (/= "零" TempStr)
        (setq TempStr (strcat TempStr "万"))
              )
      )
                 )
          (setq tempa(substr CharOfCash  1 2))
          (setq CharOfCash(if (= TempStr "零")
                              (cond
                               ((= tempa "零")CharOfCash)
                               ((= tempa "")CharOfCash)
                               ((= tempa "万")CharOfCash)
                               ((= tempa "亿")CharOfCash)
                               (t (strcat TempStr CharOfCash))
                               )
              (strcat TempStr CharOfCash)
			    ))
          )
  (setq temp(substr CharOfCash 1 4))
  (if (= "壹拾" temp)(substr CharOfCash 3)CharOfCash)

  (_n2big CharOfCash)
  )
