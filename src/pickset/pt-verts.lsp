(defun pickset:pt-verts (ss / i listpp a b c d)
  "取点"
  (setq i 0 listpp nil)
  (if ss (repeat (sslength ss)
      (setq a (ssname ss i))
      (setq b (entget a))
      (setq ename (cdr (assoc 0 b)))
      (cond ((or nil (= ename "POLYLINE")
      (= ename "LWPOLYLINE"))
          (progn (setq c (getlistofpline a))
      (setq listpp (append c listpp))))
    ((= ename "LINE")
          (progn (setq c (cdr (assoc 10 b)))
      (setq d (cdr (assoc 11 b)))
      (setq listpp (cons c listpp))
      (setq listpp (cons d listpp))))
    ((= ename "POINT")
          (progn (setq c (cdr (assoc 10 b)))
      (setq listpp (cons c listpp)))))
      (setq i (1+ i))))
  listpp)
