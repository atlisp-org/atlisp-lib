(defun dcl:img (key width height)
  "dcl 图像控件。"
  ""
  "(dcl:img \"img1 10 5)"
  (write-line (strcat ":image{key=\""
      key "\";width="
      (rtos width 2)
      ";height="
      (rtos height 2)
      ";color=152;}")
  dcl-fp))
